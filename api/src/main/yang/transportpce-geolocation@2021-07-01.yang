module transportpce-geolocation {
  yang-version 1;
  namespace "http://org/opendaylight/transportpce/geolocation";
  prefix "org-opendaylight-transportpce-geolocation";

  organization
    "transportPCE";
  contact
    "transportPCE committers - ODL";
  description
    "YANG definitions geolocation";

  revision 2021-07-01 {
    description
        "initial version";
  }

  container geonetwork {
    list geonodes {
      key node-id;
      leaf node-id {
        type string;
        description
          "Unique identifier for node in the network";
      }
      container geoLocation {
          description
            "GPS location";
          leaf latitude {
            type decimal64 {
              fraction-digits 16;
              range "-90 .. 90";
            }
            description
              "[From wikipedia] Latitude is an angle (defined below)
               which ranges from 0 at the Equator to 90 (North or
               South) at the poles";
          }
          leaf longitude {
            type decimal64 {
              fraction-digits 16;
              range "-180 .. 180";
            }
            description
              "[From wikipedia] The longitude is measured as the
               angle east or west from the Prime Meridian, ranging
               from 0 at the Prime Meridian to +180 eastward and
               -180 westward.";
          }
      }
    }
  }
}
